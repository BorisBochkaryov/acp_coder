-- Adapter interaction protocol
ACP

DEFINITIONS IMPLICIT TAGS ::=
BEGIN

IMPORTS
    AddressEndType, CallProgressType, FailureType, NetworkSRType,
    ReleaseType, ServiceFeatureType, SetupCRType, SetupIRType, SubsequentAddressType,
    UserDataType, SDPType, SetupAckType FROM INCS3Internals
    CallReference FROM INCS3datatypes;

-- Top level message structure for interaction with adapters
AcpMessage ::= SEQUENCE {
  uri  [0] OCTET STRING(SIZE(1..64)),
  callRef [1] CallReference,
  body [2] AcpBody
}

Strings ::= SEQUENCE OF PrintableString

AcpBody ::= CHOICE {
  setupInd             [1]  SetupIRType,
  setupIndAck          [2]  SetupAckType,
  setupReq             [3]  SetupIRType,
  setupReqAck	       [4]  SetupAckType,
  setupConf            [5]  SetupCRType,
  setupResp            [6]  SetupCRType,
  callProgressInd      [7]  CallProgressType,
  callProgressReq      [8]  CallProgressType,
  subsequentAddressInd [9]  SubsequentAddressType,
  subsequentAddressReq [10] SubsequentAddressType,
  addressEndInd        [11] AddressEndType,
  serviceFeatureInd    [12] ServiceFeatureType,
  dataInd              [13] UserDataType,
  dataReq              [14] UserDataType,
  releaseInd           [15] ReleaseType,
  releaseIndAck        [16] NULL,
  releaseReq           [17] ReleaseType,
  releaseReqAck        [18] NULL,
  failureInd           [19] FailureType,
  networkSuspendInd    [20] NetworkSRType,
  networkSuspendReq    [21] NetworkSRType,
  networkResumeInd     [22] NetworkSRType,
  networkResumeReq     [23] NetworkSRType,
  getRemoteSDPReq      [24] NULL,
  getRemoteSDPResp     [25] SDPRespType,
  acquireSDPReq        [26] NULL,
  acquireSDPResp       [27] SDPRespType,
  throughconnectReq    [28] ThroughconnectType,
  generateSignalReq    [29] SignalType,
  changeMediaInd       [30] ChangeMediaIRType,
  changeMediaReq       [31] ChangeMediaIRType,
  changeMediaConf      [32] ChangeMediaCRType,
  changeMediaResp      [33] ChangeMediaCRType,
  ...
}

SDPRespType ::= CHOICE
{
  sdp   [0] SDPType,
  error [1] NULL,
  ...
}

SDPEntry ::= SEQUENCE {name UTF8String, value UTF8String}

ThroughconnectType ::= SEQUENCE
{
  localSDP  [1] SDPRespType OPTIONAL,
  remoteSDP [2] SDPRespType OPTIONAL,
  mode      [3] MediaMode,
  ...
}

MediaMode ::= ENUMERATED
{
  sendOnly(0),
  recvOnly(1),
  sendRecv(2),
  inactive(3),
  loopBack(4),
  ...
}

ChangeMediaIRType ::= SEQUENCE
{
  reason [1] ChangeMediaReasonType,
  sdp    [2] SDPType OPTIONAL,
  ...
}

ChangeMediaReasonType ::= ENUMERATED
{
  voice(0),
  fax(1),
  ...
}

ChangeMediaCRType ::= CHOICE
{
  ok   [0] NULL,
  fail [1] ChangeMediaFailType,
  ...
}

ChangeMediaFailType ::= SEQUENCE
{
  reason [0] UTF8String,
  ...
}

SignalType ::= SEQUENCE
{
  signal    [0] Signals,
  direction [1] SignalDirection DEFAULT external,
  ...
}

Signals ::= ENUMERATED
{
  dialTone(0),
  ringingTone(1),
  busyTone(2),
  congestionTone(3),
  specialInformationTone(4),
  warningTone(5),
  payphoneRecognitionTone(6),
  callWaitingTone(7),
  callerWaitingTone(8),
  payTone(9),
  ...
}

SignalDirection ::= ENUMERATED
{
  external(0), -- направление сигнала по умолчанию, направление на физический порт/линию от MG
  internal(1), -- направление сигнала ко всем терминация в контексте (в RTP)
  both(2)      -- направление сигнала как в линию, так и к терминациям
}

ANYPACK ::= SEQUENCE {
  arg   [0] BIT STRING
}

END
