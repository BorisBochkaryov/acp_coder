INCS3Internals

DEFINITIONS IMPLICIT TAGS ::=
BEGIN
IMPORTS

    CalledPartyNumber,
    CalledPartysCategory,
    CallingPartyNumber,
    CallingPartysCategory,
    TrunkGroupId,
    CallTransferNumber,
    OriginalCalledNumber,
    ACPDestinationRoutingAddress,
    RedirectingNumber,
    ACPRedirectionInformation,
    OptionalBackwardCallInidicators,
    GenericNotificationIndicatorList,
    RedirectionNumber
    FROM ACPdatatypes

    AdditionalInformation,
    Cause,
    CollectInformation,
    Digits,
    DTLegType,
    EventTypeBCSM,
    EventTypeCharging,
    FacilityGroup,
    ForwardCallIndicators,
    GenericNumbers,
    DTLegID,
    MonitorMode,
    OriginalCalledPartyID,
    RedirectingPartyID,
    RedirectionInformation,
    RouteList,
    ServiceKey,
    USIServiceIndicator,
    USIInformation
    FROM INCS3datatypes;
    -- DEFINITION OF SIGNALLING CONTROL PRIMITIVES

CallFlag ::= ENUMERATED { -- Note: Used on the signals between BCSMs.
                          senderRef(0),
                          receiverRef(1)
                        }

CallRef ::= INTEGER

InfoDirection ::= ENUMERATED {
  utsi(0),
  stui(1)
}

AddressEndType ::= SEQUENCE {
  callRef [0] CallRef,
  digits  [1] Digits OPTIONAL
}
CauseInitiator ::= ENUMERATED {
  user(0),
  isupNetwork(1),
  nonIsupNetwork(2),
  system(3)
}
EventIndicator ::= ENUMERATED {
  alerting(0),
  progress(1),
  inBandInfo(2),
  cfb(3),
  cfnr(4),
  cfu(5)
}
EventPresentationRestrictedIndicator ::= ENUMERATED {
  noIndication(0),
  restricted(1)
}
EventInformation ::= SEQUENCE {
  eventIndicator                [0] EventIndicator,
  eventPresentationIndicator    [1] EventPresentationRestrictedIndicator
}
RedirectionRestrictionIndicator ::= ENUMERATED {
  presentationAllowed(0),
  presentationRestricted(1)
}
NotificationSubscriptionOptions ::= ENUMERATED {
  unknown(0),
  presentationNotAllowed(1),
  presentationAllowedWithRedirectingNumber(2),
  presentationAllowedWithoutRedirectingNumber(3)
}
RedirectingReason ::= ENUMERATED {
  unknown(0),
  busy(1),
  noReply(2),
  unconditional(3),
  deflectAlert(4),
  deflectResp(5),
  notReachable(6),
  timeOfDay(7),
  doNotDisturb(8),
  followMe(9),
  outOfService(10),
  away(11)
}
CallDiversionInformation ::= SEQUENCE {
  notificationSubsOpts  [0] NotificationSubscriptionOptions,
  redirectingReason     [1] RedirectingReason
}
CallProgressType ::= SEQUENCE {
  cause                 [0] Cause,
  causeInitiator        [1] CauseInitiator,
  causeIsup             [2] BIT STRING                          OPTIONAL,
  eventInformation      [3] EventInformation                    OPTIONAL,
  additionalInfo        [4] SEQUENCE OF AdditionalInformation   OPTIONAL,
  oBCI                  [5] OptionalBackwardCallInidicators     OPTIONAL, -- optioanl backward call indicators
  gNotification         [6] GenericNotificationIndicatorList    OPTIONAL, -- list of Generic Notification Indicator
  redirectionNumber     [7] RedirectionNumber                   OPTIONAL,
  redirectionRestInd    [8] RedirectionRestrictionIndicator     OPTIONAL,
  callDiversionInfo     [9] CallDiversionInformation            OPTIONAL,
  facility              [10] OCTET STRING                       OPTIONAL,
  sdp                   [11] SDPType                            OPTIONAL,
  mediaPoint            [12] BIT STRING                         OPTIONAL,
  trunkGroupId          [13] TrunkGroupId                       OPTIONAL,
  callTransferNumber    [14] CallTransferNumber                 OPTIONAL,
  refer                 [15] ReferType                          OPTIONAL,
  eventTime             [16] EventTime                          OPTIONAL
}

FailureType ::= SEQUENCE {
  callRef  [0] CallRef,
  cause    [1] Cause
}

NetworkSRType ::= SEQUENCE {
  callRef [0] CallRef
}

ReleaseType ::= SEQUENCE {
  cause            [0] Cause,
  causeInitiator   [1] CauseInitiator,
  dialledDigits    [2] PrintableString          OPTIONAL,
  causeIsup        [3] BIT STRING               OPTIONAL,
  additionalInfo   [4] SEQUENCE OF AdditionalInformation    OPTIONAL,
  trunkGroupId     [5] TrunkGroupId             OPTIONAL,
  sid              [6] BIT STRING               OPTIONAL,
  refer            [7] ReferType                OPTIONAL,
  needAck          [8] BOOLEAN,
  eventTime        [9] EventTime                OPTIONAL
}

ServiceFeatureType ::= SEQUENCE {
  cause      [0] ENUMERATED {
    flash(0),
    refer(1)
  },
  callRef    [1] SEQUENCE OF AdditionalInformation OPTIONAL
}

SetupCRType ::= SEQUENCE {
  connectedNumber       [0] CallingPartyNumber OPTIONAL,
  additionalInfo        [1] SEQUENCE OF AdditionalInformation,
  redirectionNumber     [2] RedirectionNumber OPTIONAL,
  redirectionRestInd    [3] RedirectionRestrictionIndicator OPTIONAL,
  sdp                   [4] SDPType OPTIONAL,
  mediaPoint            [5] BIT STRING OPTIONAL,
  refer                 [6] ReferType OPTIONAL,
  eventTime             [7] EventTime
}

--SDPType ::= SEQUENCE {
--  type      [0] ENUMERATED {
--    offer(0),
--    answer(1),
--    unknown(2)
--  },
--  body      [1] BIT STRING
--}

SDPType ::= SEQUENCE {
  type              [0] ENUMERATED {
    offer(0),
    answer(1),
    unknown(2)
  } OPTIONAL,
  sdp              [1] SEQUENCE OF SEQUENCE {
    version             [1] OCTET STRING OPTIONAL,
    origin              [2] SEQUENCE {
        prefix   [1] OCTET STRING,
        first    [2] OCTET STRING,
        second   [3] OCTET STRING,
        to       [4] OCTET STRING,
        proto    [5] OCTET STRING,
        ip       [6] OCTET STRING
    } OPTIONAL,
    atr1                [3] OCTET STRING OPTIONAL,
    atr2                [4] OCTET STRING OPTIONAL,
    atr3                [5] OCTET STRING OPTIONAL,
    atr4                [6] OCTET STRING OPTIONAL,
    atr5                [7] OCTET STRING OPTIONAL,
    connection          [8] SEQUENCE { -- TODO: вместо undefined подставляется <<>>
        to      [1] OCTET STRING,
        proto   [2] OCTET STRING,
        ip      [3] OCTET STRING
    } OPTIONAL,
    atr6                [9] SEQUENCE OF OCTET STRING OPTIONAL,
    atr7                [10] OCTET STRING OPTIONAL,
    atr8                [11] SEQUENCE OF OCTET STRING OPTIONAL,
    atr9                [12] OCTET STRING OPTIONAL,
    atr10               [13] OCTET STRING OPTIONAL,
    attribute           [14] SEQUENCE OF SEQUENCE {
        atr1            [0] OCTET STRING OPTIONAL,
        atr2            [1] OCTET STRING OPTIONAL,
        types           [2] ENUMERATED {
            session(0)
        } OPTIONAL
    } OPTIONAL,
    media-description   [15] SEQUENCE OF SEQUENCE {
        media       [0] SEQUENCE {
            arg1        [0] OCTET STRING OPTIONAL,
            arg2        [1] OCTET STRING OPTIONAL,
            arg3        [2] OCTET STRING OPTIONAL,
            arg4        [3] OCTET STRING OPTIONAL,
            format      [4] SEQUENCE OF SEQUENCE {
                arg1        [0] OCTET STRING OPTIONAL,
                arg2        [1] OCTET STRING OPTIONAL,
                arg3        [2] OCTET STRING OPTIONAL,
                arg4        [3] OCTET STRING OPTIONAL,
                arg5        [4] OCTET STRING OPTIONAL,
                arg6        [5] BOOLEAN OPTIONAL,
                arg7        [6] BOOLEAN OPTIONAL
            } OPTIONAL
        },
        arg1        [1] OCTET STRING OPTIONAL,
        connection  [2] SEQUENCE { -- TODO: <<>> вместо undefined
            to          [0] OCTET STRING OPTIONAL,
            prot        [1] OCTET STRING OPTIONAL,
            ip          [2] OCTET STRING OPTIONAL
        } OPTIONAL,
        arg2        [3] SEQUENCE OF OCTET STRING OPTIONAL,
        arg3        [4] OCTET STRING OPTIONAL,
        attribute   [5] SEQUENCE OF SEQUENCE {
            arg1        [0] OCTET STRING OPTIONAL, -- сделать обязательный перевод в строку
            arg2        [1] OCTET STRING OPTIONAL,
            arg3        [2] ENUMERATED {
                session(0),
                media(1)
            } OPTIONAL
        } OPTIONAL
    }
  } OPTIONAL
}

ReferType ::= SEQUENCE {
  exchange      [0] OCTET STRING,
  routingKey    [1] OCTET STRING OPTIONAL,
  sid           [2] BIT STRING OPTIONAL,
  callRef       [3] OCTET STRING OPTIONAL,
  confId        [4] OCTET STRING OPTIONAL
}

SetupAckType ::= SEQUENCE {
  refer         [0] ReferType OPTIONAL,
  trunkGroupId  [1] TrunkGroupId OPTIONAL
}

SetupModeType ::= ENUMERATED {
  normal(0),
  dummy(1),
  internal(2),
  callback(3),
  parking(4),
  supervice(5),
  acd(6)
}

SetupIRType ::= SEQUENCE {
  domain                      [0] PrintableString,
  calledPartyNumber           [1] CalledPartyNumber      OPTIONAL,
  calledPartysCategory        [2] CalledPartysCategory   OPTIONAL,
  callingPartyNumber          [3] CallingPartyNumber     OPTIONAL,
  callingPartysCategory       [4] CallingPartysCategory  OPTIONAL,
  locationNumber              [5] OCTET STRING           OPTIONAL,
  originalCalledNumber        [6] OriginalCalledNumber   OPTIONAL,
  userTeleserviceInformation  [7] OCTET STRING           OPTIONAL,
  genericNumber               [8] GenericNumbers         OPTIONAL,
  forwardCallIndicators       [9] SEQUENCE OF INTEGER    OPTIONAL,
  redirectingNumber          [10] RedirectingNumber      OPTIONAL,
  redirectingInformation     [11] RedirectionInformation OPTIONAL,
  uSIServiceIndicator        [12] USIServiceIndicator    OPTIONAL,
  uSIInformation             [13] USIInformation         OPTIONAL,
  isupCallRef                [14] OCTET STRING           OPTIONAL,
  sdp                        [15] SDPType                OPTIONAL,
  mediaPoint                 [16] OCTET STRING           OPTIONAL,
  additionalInfo             [17] SEQUENCE OF AdditionalInformation,
  trunkGroupId               [18] TrunkGroupId           OPTIONAL,
  callingPartyInfo           [19] SEQUENCE OF PrintableString,
  calledPartyInfo            [20] SEQUENCE OF PrintableString,
  callingIfaceInfo           [21] SEQUENCE OF PrintableString,
  calledIfaceInfo            [22] SEQUENCE OF PrintableString,
  refer                      [23] CHOICE {
    refer           [0] SEQUENCE OF CHUNT
  } OPTIONAL,
  mode                       [24] SetupModeType          OPTIONAL,
  eventTime                  [25] EventTime OPTIONAL
}

CHUNT ::= SEQUENCE {
  chunt-refer     [0] CHOICE {
    chunt-refer [0] SEQUENCE OF OCTET STRING
  }
}

SubsequentAddressType ::= SEQUENCE {
  callRef [0] CallRef,
  digits  [1] Digits
}

UserDataType ::= SEQUENCE {
  callRef             [0] CallRef,
  uSIServiceIndicator [1] USIServiceIndicator,
  uSIInformation      [2] USIInformation,
  infoDirection       [3] InfoDirection
}



-- DEFINITION OF THE INFORMATIVE MANAGEMENT OPERATION ARGUMENTS

MGTSetTriggerTableArg ::= SEQUENCE OF SEQUENCE {
  legID         [0] DTLegType,
  serviceKey    [1] ServiceKey,
  eventTypeBCSM [2] EventTypeBCSM,
  monitorMode   [3] MonitorMode
}



-- DEFINITION OF TYPES USED INTERNALLY IN THE SDL SPECIFICATION

BCSMStateType ::= ENUMERATED {
  nullState(0),                 -- Normal case
  waitOrigAttemptAuthorized(1), -- Used with ICA
  analyseInformation(2),        -- Used with Connect, AnalyseInformation
  waitMidCall(3),               -- Used with Connect
  selectRoute (4),              -- Used with Connect, SelectRoute
  origAttempt (5),              -- Used with Connect
  collectInfo (6)       -- Used with CollectInformation
}

DPFacilityArg ::= SEQUENCE {
  legID               DTLegType,
  party               PartyType
}



PartyType ::= ENUMERATED {
  localParty(0),
  remoteParty(1),
  surrogateParty(2)
}

DPArg ::= SEQUENCE {
  legID                       [0] DTLegType,
  bcsmEvent                   [1] EventTypeBCSM,
  party                       [2] PartyType               OPTIONAL,
  cgPN                        [3] CallingPartyNumber      OPTIONAL,
  cdPN                        [4] CalledPartyNumber       OPTIONAL,
  callingPartysCategory       [5] CallingPartysCategory   OPTIONAL,
  locationNumber              [6] OCTET STRING            OPTIONAL,
  originalCalledNumber        [7] OriginalCalledNumber   OPTIONAL,
  userTeleserviceInformation  [8] OCTET STRING            OPTIONAL,
  genericNumber               [9] GenericNumbers          OPTIONAL,
  forwardCallIndicators      [10] ForwardCallIndicators   OPTIONAL,
  redirectingNumber          [11] RedirectingPartyID      OPTIONAL,
  redirectingInformation     [12] RedirectionInformation  OPTIONAL,
  uSIServiceIndicator        [13] USIServiceIndicator     OPTIONAL,
  uSIInformation             [14] USIInformation          OPTIONAL,
  digits                     [15] Digits                  OPTIONAL,
  cause                      [16] Cause                   OPTIONAL
}

DPUTSIArg ::= SEQUENCE {
  legID               [0] DTLegType,
  uSIServiceIndicator [1] USIServiceIndicator,
  uSIInformation      [2] USIInformation,
  party               [3] PartyType
}

emptyString OCTET STRING ::= ''H

oct0 OCTET STRING ::= '00'H
oct1 OCTET STRING ::= '01'H
oct2 OCTET STRING ::= '02'H
oct3 OCTET STRING ::= '03'H
oct4 OCTET STRING ::= '04'H
oct5 OCTET STRING ::= '05'H
oct6 OCTET STRING ::= '06'H
oct7 OCTET STRING ::= '07'H
oct8 OCTET STRING ::= '08'H
oct9 OCTET STRING ::= '09'H
octa OCTET STRING ::= '0A'H
octb OCTET STRING ::= '0B'H


OBCSMPars ::= SEQUENCE {
  startState              [0] BCSMStateType,
  legID                   [1] DTLegType,
  cgPN                    [2] CallingPartyNumber OPTIONAL,
  routingInfo             [3] CHOICE {
    cdPN            [0] CalledPartyNumber,
    routingAddress  [1] ACPDestinationRoutingAddress
  },
  routeList                   [4] RouteList              OPTIONAL,
  callingPartysCategory       [5] CallingPartysCategory  OPTIONAL,
  locationNumber              [6] OCTET STRING           OPTIONAL,
  originalCalledNumber        [7] OriginalCalledNumber  OPTIONAL,
  userTeleserviceInformation  [8] OCTET STRING           OPTIONAL,
  genericNumber               [9] GenericNumbers         OPTIONAL,
  forwardCallIndicators      [10] ForwardCallIndicators  OPTIONAL,
  redirectingNumber          [11] RedirectingPartyID     OPTIONAL,
  redirectingInformation     [12] RedirectionInformation OPTIONAL,
  uSIServiceIndicator        [13] USIServiceIndicator    OPTIONAL,
  uSIInformation             [14] USIInformation         OPTIONAL,
  setupTime                  [15] EventTime              OPTIONAL
}

PointInCall ::= ENUMERATED {
  analyseInformation(0),
  authoriseOriginationAttempt(1),
  collectInformation(2),
  collectNDigits(3),
  oActive(4),
  oAlerting(5),
  oException(6),
  oNull(7),
  selectRoute(8),
  sendCall(9),
  authoriseTerminationAttempt(10),
  presentCall(11),
  selectFacility(12),
  tActive(13),
  tAlerting(14),
  tNull(15),
  releaseCall(16),         -- Used with the ReleaseCall operation

  disconnectLeg(17),       -- Note: IN CS-2 PIC
  sendSTUI(18),            -- Note: IN CS-2 PIC
  sendUTSI(19),            -- Note: IN CS-2 PIC
  authorizeTermination(20),-- Note: IN CS-2 PIC
  reconnect(21)        -- Note: IN CS-3
}

ChargingEventIndArg ::= SEQUENCE {
  callRef                     [0] CallRef,
  eventTypeCharging           [1] EventTypeCharging
}

PICArg ::= SEQUENCE {
  legID                       [0] DTLegType,
  pic                         [1] PointInCall,
  routingInfo                 [2] CHOICE {
    cdPN           [0] CalledPartyNumber,
    routingAddress [1] ACPDestinationRoutingAddress
  },
  routeList                   [3] RouteList               OPTIONAL,
  callingPartyNumber          [4] CallingPartyNumber      OPTIONAL,
  callingPartysCategory       [5] CallingPartysCategory   OPTIONAL,
  locationNumber              [6] OCTET STRING            OPTIONAL,
  originalCalledNumber        [7] OriginalCalledPartyID   OPTIONAL,
  userTeleserviceInformation  [8] OCTET STRING            OPTIONAL,
  genericNumber               [9] GenericNumbers          OPTIONAL,
  forwardCallIndicators      [10] ForwardCallIndicators   OPTIONAL,
  redirectingNumber          [11] RedirectingPartyID      OPTIONAL,
  redirectingInformation     [12] RedirectionInformation  OPTIONAL,
  uSIServiceIndicator        [13] USIServiceIndicator     OPTIONAL,
  uSIInformation             [14] USIInformation          OPTIONAL,
  infoDirection              [15] InfoDirection           OPTIONAL,
  party                      [16] PartyType               OPTIONAL,
  facilityGroup              [17] FacilityGroup           OPTIONAL,
  cause                      [18] Cause                   OPTIONAL
}

-- contain result of erlang:now() - {MeSec, Sec, MiSec}
EventTime ::= SEQUENCE {
    megaSec     [0] INTEGER,
    sec         [1] INTEGER,
    micSec      [2] INTEGER
}

END
